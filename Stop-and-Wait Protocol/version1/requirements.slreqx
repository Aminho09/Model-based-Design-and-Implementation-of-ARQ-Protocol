# requirements

## 1: Sender Component Requirements (Functional)

### 1.1: Input Interface Requirements (Functional)

#### 1.1.1: Defining 'data' input port (Functional)
The Sender component shall have an input port named data to receive data from the upper layer.

#### 1.1.2: Defining 'SendBackBus' input port (Functional)
The Sender shall have an input port named SendBackBus to receive acknowledgments from the ReceiveChannel.

### 1.2: Data Handling Requirements (Functional)

#### 1.2.1: Sender should add a sequence number (Functional)
Upon receiving data from the upper layer via data, the Sender shall assign a sequence number to the data packet. The sequence number shall toggle between 0 and 1 (for binary sequence numbering).

#### 1.2.2: Sender should add a header to indicate it is a data packet (Functional)
The Sender shall create a data packet that includes a header to indicate it is a data packet.

#### 1.2.3: Sender should add checksum (Functional)
The Sender shall calculate a checksum for the entire packet to ensure data integrity.

#### 1.2.4: Sender should transmit the packet to the SendChannel (Functional)
The Sender shall transmit the data packet to the SendChannel component via SendInBus. The data packet shall include the type identifier in the header, the sequence number, the payload, and the checksum.

### 1.4: Timeout Mechanism (Functional)
The Sender shall implement a configurable timeout mechanism to detect lost packets.

#### 1.4.1: Timeout period (Functional)
The timeout period shall be configurable based on network conditions, typically up to 4 seconds.

#### 1.4.2: Sender should resend the data if timeout reached (Functional)
If an ACK is not received within the timeout period, the Sender shall retransmit the data packet.

#### 1.4.3: Raise an error if the maximum number of timeout is exceeded (Functional)
The Sender shall maintain a counter to track the number of retransmission attempts and shall trigger an error if the maximum number is exceeded.

### 1.5: ACK Handling (Functional)

#### 1.5.1: Sender should verify ACK's correctness (Functional)
Upon receiving an ACK, the Sender shall verify its correctness by checking the sequence number and checksum.

#### 1.5.2: Sender should clear the buffer if the ACK was valid (Functional)
If the ACK is valid, the Sender shall clear the current buffer and become ready to accept new data from the upper layer.

#### 1.5.3: Sender should ignore the invalid ACK (Functional)
If the ACK is invalid (incorrect sequence number or checksum), the Sender shall ignore it and continue waiting for a valid ACK.

## 2: Receiver Component Requirements (Functional)

### 2.1: Input Interface Requirements (Functional)
The Receiver must have an input port ReceiveInBus to receive the data from the ReceiveChannel. The data received should include the payload, sequence number, and checksum.

### 2.2: Data Handling Requirements (Functional)

### 2.3: ACK Generation (Functional)

#### 2.3.1: Receiver should generate an ACK if data was valid (Functional)
Upon successful receipt of a valid data packet, the Receiver shall generate an acknowledgment (ACK).

#### 2.3.2: The Ack should have a header, a sequence number, and a checksum (Functional)
The ACK message generated shall include a header/type identifier indicating it is an ACK, along with the sequence number and checksum.

#### 2.3.3: Receiver should send the ACK to SendChannel (Functional)
The Receiver shall send the ACK back to the Sender component using the SendChannel.

### 2.4: Handling Duplicate Packets (Functional)

#### 2.4.1: Receiver shouldn't process a duplicate data packet (Functional)
If the Receiver receives a duplicate data packet (same sequence number as the last valid packet), it shall not process the data again.

#### 2.4.2: Receiver should resend the last ACK if received a duplicate packet. (Functional)
The Receiver shall resend the last ACK to the Sender without processing the duplicate packet.

## 3: SendChannel Component Requirements (Functional)

### 3.1: Input Interface Requirements (Functional)

#### 3.1.1: Defining 'SendInBus' input port (Functional)
The SendChannel component shall have an input port named SendInBus to receive data packets from the Sender component.

#### 3.1.2: Defining 'ReceiveBackBus' input port (Functional)
The SendChannel component shall have an input port named ReceiveBackBus to receive ACKs from the Receiver component.

### 3.2: Data Transmission (Functional)

#### 3.2.1: SendChannel should transmit the packet using a UDP Send block (Functional)
The SendChannel shall transmit the received message using a UDP Send block. The UDP Send block shall be configured to send messages to the network address of the corresponding ReceiveChannel component.

#### 3.2.2: ACKs has higher priority than datas (Functional)
If a data and an ACK arrived at the same time in SendChannel component, the component should hold the data in a buffer and transmit the ACK first, then send the data buffered.

## 4: ReceiveChannel Component Requirements (Functional)

### 4.1: Input Interface Requirements (Functional)
The ReceiveChannel component shall have a single input port ReceiveInBus which receives both data packets and ACKs from the SendChannel component via a UDP Receive block.

### 4.3: Packet Forwarding (Functional)

#### 4.2.1: ReceiveChannel should distinguish between data packet and ACK (Functional)
Upon receiving a message via ReceiveInBus, the ReceiveChannel shall first extract and analyze the header/type identifier to determine the nature of the message:
- Data Packet: If the header/type identifier is 0, the message is identified as a data packet.
- ACK: If the header/type identifier is 1, the message is identified as an ACK.

#### 4.3.2: ReceiveChannel should forward the message to the appropriate component (Functional)
Depending on the message type, the ReceiveChannel shall forward the message to the appropriate component:
- Data Packet: The message shall be forwarded to the Receiver component via the SendBackBus port.
- ACK: The message shall be forwarded to the Sender component via the ReceiveInBus port.

### 4.2: Packet Processing (Functional)

#### 4.2.1: Receiver should verify the sequence number (Functional)
Upon receiving a data packet, the ReceiveChannel shall verify the sequence number to ensure the correct order.

#### 4.2.3: Receiver should forward the payload to the upper layer if the data was valid (Functional)
If the checksum and sequence number are valid, the ReceiveChannel shall extract the payload from the data packet and forward the payload to the appropriate component through an output port.

#### 4.2.2: Receiver should verify the checksum (Functional)
The ReceiveChannel shall calculate the checksum of the received data packet and compare it with the transmitted checksum.

#### 4.2.4: Receiver should discard the data if the data packet was invalid (Functional)
If the data packet is invalid (incorrect sequence number or checksum), the ReceiveChannel shall discard it and not forward it to the appropriate component.
