# requirements

## #1: Sender Component Requirements (Functional)

### #4: ACK Handling Requirements (Functional)

### #8: Creating Packet (Functional)
The Sender component shall select the first data in the buffer and compute a CRC-based error detection header and concatenate it with the selected data to create an uint16 packet for transmission.

### #12: Buffering Input Data (Functional)
The Sender component shall accept a uint8 input data and append it to a buffer when input data is present.

### #13: Sending the Packet (Functional)
The Sender component shall transmit the packet via a UDP Send block to the Receiver.

### #14: Timeout Mechanism (Functional)
The Sender component shall initiate a timer after sending the packet and wait for an acknowledgment (ACK) from the Receiver. The Sender component shall resend the packet if the ACK is not received within 4 seconds. The retransmission process shall repeat until an ACK is received for the corresponding data packet.

### #15: Removing transmited data (Functional)
The Sender component shall remove the data from the buffer when a valid ACK is received.

## #5: Receiver Component Requirements (Functional)

### #16: Receiving the Packet (Functional)
The Receiver component shall receive packets via the UDP Receive block from the Sender.

### #17: Checking error header (Functional)
The Receiver component shall check the CRC-based error detection header of the received packet.

### #18: Corrupted Packet Mechanism (Functional)
If the error detection bits are incorrect, the Receiver component shall discard the packet and not generate an ACK.

### #19: Incorrupted Packet Mechanism (Functional)
If the error detection bits are correct, the Receiver component shall strip the header and send the data to the output.

### #20: Generating the ACK (Functional)
The Receiver component shall generate an acknowledgment (ACK) and send it back to the Sender via the UDP Send block.
